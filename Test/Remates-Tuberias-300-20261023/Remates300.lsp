(setq rt300-specs '(("1A34F" ((579214.316928736866 8302239.888303650543) (579213.907394000096 8302225.542721740901)) ((579214.215757473372 8302225.831404358149) (579214.207196288509 8302225.531514856964) (579213.607591711683 8302225.553928624839) (579213.616152894916 8302225.853818126023)) 2442.000000000000)
("1A34E" ((579229.501764069661 8302246.148830973543) (579228.903248877265 8302225.183457474224)) ((579229.211612350540 8302225.472140091471) (579229.203051165678 8302225.172250590287) (579228.603446588852 8302225.194664358161) (579228.612007772084 8302225.494553859346)) 2442.000000000000)
("1A34D" ((579244.686599402456 8302252.409358299337) (579244.370630853460 8302241.341304008849)) ((579244.678994326736 8302241.629986626096) (579244.670433141873 8302241.330097124912) (579244.070828565047 8302241.352510892786) (579244.079389748280 8302241.652400393970)) 2442.000000000000)
("1A34C" ((579216.107972792932 8302240.626729850657) (579198.770262432983 8302253.654981761239)) ((579198.827768670511 8302253.236509876326) (579198.587925228756 8302253.416737873107) (579198.952599637210 8302253.893225649372) (579199.192443079315 8302253.712997655384)) 2442.000000000000)
("1A34B" ((579232.231125917751 8302247.274114459753) (579216.887043143623 8302258.804274529219)) ((579216.944549381151 8302258.385802644305) (579216.704705939395 8302258.566030641086) (579217.069380347850 8302259.042518417351) (579217.309223789955 8302258.862290423363)) 2442.000000000000)
("1A34A" ((579248.354279041872 8302253.921499070711) (579235.003823853447 8302263.953567300923)) ((579235.061330090975 8302263.535095416009) (579234.821486649220 8302263.715323412791) (579235.186161057674 8302264.191811189055) (579235.426004499779 8302264.011583195068)) 2442.000000000000)
("1A348" ((579318.488020657678 8302315.916792500764) (579332.432990302448 8302313.280225072987)) ((579332.196535754134 8302313.630246403627) (579332.491324748727 8302313.574510816485) (579332.374655856169 8302312.985939329490) (579332.079866861925 8302313.041674915701)) 0.000000000000)
("1A347" ((579306.586689041927 8302302.901220198721) (579327.564187752083 8302299.042742269114)) ((579327.325999080786 8302299.391585847363) (579327.621061041835 8302299.337313883007) (579327.507314462331 8302298.748170655221) (579327.212252501748 8302298.802442618646)) 0.000000000000)
("1A346" ((579294.685357425944 8302289.885647898540) (579321.177631990053 8302284.876768711954)) ((579320.941177441739 8302285.226790042594) (579321.235966436332 8302285.171054455452) (579321.119297543773 8302284.582482968457) (579320.824508549529 8302284.638218554668)) 0.000000000000)
("1A345" ((579213.442908241879 8302304.671145985834) (579231.596289132955 8302317.665788982995)) ((579213.859327582875 8302304.600289667957) (579213.615375765949 8302304.425662871450) (579213.270440717810 8302304.916629100218) (579213.514392533107 8302305.091255897656)) 2442.000000000000)
("1A344" ((579259.102451926214 8302286.785159709863) (579264.787590305903 8302264.275555565022)) ((579258.884402881726 8302286.423385886475) (579258.810937358765 8302286.714263564907) (579259.393966493662 8302286.856055854820) (579259.467432018020 8302286.565178177319)) 0.000000000000)
("1A343" ((579246.556521772523 8302293.476182629354) (579242.802644905401 8302326.498309312388)) ((579242.538152085268 8302326.168962636031) (579242.504265718628 8302326.467054435983) (579243.101024092175 8302326.529564188793) (579243.134910460212 8302326.231472389773)) 2442.000000000000)
("1A342" ((579236.936265828088 8302314.185123531148) (579217.937110804603 8302326.569016995840)) ((579218.022411000682 8302326.155314734206) (579217.771076526260 8302326.319137775339) (579218.103145082947 8302326.818896216340) (579218.354479557602 8302326.655073176138)) 2442.000000000000)
("1A341" ((579225.060757909203 8302383.035666788928) (579223.026598396711 8302417.745500282384)) ((579222.744509363431 8302417.431093757972) (579222.726957384031 8302417.730591563508) (579223.326239409391 8302417.760409001261) (579223.343791390420 8302417.460911198519)) 2442.000000000000)
("1A340" ((579228.763558844803 8302376.959023195319) (579206.776347129489 8302371.155760256574)) ((579207.140425168676 8302370.941580737010) (579206.850347291562 8302370.865018133074) (579206.702346967417 8302371.446502380073) (579206.992424843367 8302371.523064984940)) 2442.000000000000)
("1A33F" ((579220.620031440165 8302390.323315389454) (579199.116888437187 8302384.647816631943)) ((579199.480966476258 8302384.433637112379) (579199.190888599143 8302384.357074508443) (579199.042888275231 8302384.938558755443) (579199.332966151065 8302385.015121360309)) 2442.000000000000)
("1A33D" ((579275.486622036085 8302223.119109177031) (579271.105698934640 8302241.792690468021)) ((579270.881548242061 8302241.434665116481) (579270.813024389907 8302241.726746421307) (579271.398373479373 8302241.858634514734) (579271.466897332924 8302241.566553209908)) 2442.000000000000)
("1A33C" ((579288.883145465399 8302215.373417589813) (579292.015781084890 8302248.001377625391)) ((579291.688734793686 8302247.734045605175) (579291.717407297692 8302248.032684006728) (579292.314154872089 8302247.970071244054) (579292.285482369713 8302247.671432844363)) 2442.000000000000)
("1A33B" ((579306.495891368366 8302241.868038368411) (579307.280487796059 8302250.040000894107)) ((579306.953441504855 8302249.772668873891) (579306.982114008861 8302250.071307275444) (579307.578861583257 8302250.008694512770) (579307.550189080881 8302249.710056113079)) 2442.000000000000)
("1A33A" ((579268.600814268808 8302227.696565995924) (579248.587515936350 8302208.355290501378)) ((579249.009823083761 8302208.346215335652) (579248.794091711752 8302208.137727969326) (579248.380940160947 8302208.572853033431) (579248.596671530977 8302208.781340401620)) 2442.000000000000)
("1A339" ((579281.389092743513 8302219.195342249237) (579256.003030396649 8302194.661713787355)) ((579256.425337544060 8302194.652638621628) (579256.209606172051 8302194.444151255302) (579255.796454621246 8302194.879276319407) (579256.012185991276 8302195.087763687596)) 2442.000000000000)
("1A337" ((579304.999223970808 8302239.616621389985) (579316.785310328123 8302237.770602355711)) ((579316.537949597347 8302238.113003223203) (579316.834347683121 8302238.066579286940) (579316.736272973125 8302237.474625424482) (579316.439874887932 8302237.521049357019)) 2442.000000000000)
("1A336" ((579295.904760368168 8302225.935940044932) (579311.717486195033 8302223.296182798222)) ((579311.473578585545 8302223.641051995568) (579311.769495213637 8302223.591652032919) (579311.665477176430 8302223.000713563524) (579311.369560549152 8302223.050113525242)) 2442.000000000000)
("1A335" ((579286.810296766693 8302212.255258699879) (579312.531334079453 8302207.927678614855)) ((579312.287866714410 8302208.272858752869) (579312.583720068214 8302208.223081246018) (579312.478948090691 8302207.632275983691) (579312.183094737586 8302207.682053488679)) 2442.000000000000)
("1A333" ((579233.842058924143 8302352.389485468157) (579256.940691688564 8302297.853143040091)) ((579233.681789226830 8302351.998666699976) (579233.564782850794 8302352.274921139702) (579234.119334997493 8302352.504049796611) (579234.236341374810 8302352.227795359679)) 2469.000000000000)
("1A332" ((579253.518259196542 8302382.855454805307) (579266.867131969426 8302351.338494299911)) ((579253.357989499229 8302382.464636037126) (579253.240983123193 8302382.740890476853) (579253.795535269892 8302382.970019133762) (579253.912541647209 8302382.693764696829)) 2469.000000000000)
("1A331" ((579238.456261037849 8302379.956199767999) (579261.903911828878 8302324.595818671398)) ((579238.295991340536 8302379.565380999818) (579238.178984964499 8302379.841635439545) (579238.733537111199 8302380.070764096454) (579238.850543488516 8302379.794509659521)) 2469.000000000000)
("1A330" ((579256.469022260862 8302274.891529330052) (579252.383164043305 8302266.489293581806)) ((579252.782998880604 8302266.625520555303) (579252.651798612438 8302266.355717855506) (579252.114529474173 8302266.622869308107) (579252.245729740709 8302266.892672007903)) 0.000000000000)
("1A32F" ((579241.170233750483 8302277.730858360417) (579234.971682080533 8302264.984040029347)) ((579235.371516917832 8302265.120267002843) (579235.240316649666 8302264.850464303046) (579234.703047511401 8302265.117615755647) (579234.834247777937 8302265.387418455444)) 0.000000000000)
("1A32E" ((579224.073612169595 8302276.873089621775) (579215.617083566962 8302259.482925022952)) ((579216.016918404261 8302259.619151996449) (579215.885718136095 8302259.349349296652) (579215.348448997829 8302259.616500749253) (579215.479649264365 8302259.886303449050)) 0.000000000000)
("1A32D" ((579206.688647955656 8302275.422367666848) (579196.262485053740 8302253.981810020283)) ((579196.662319891038 8302254.118036993779) (579196.531119622872 8302253.848234293982) (579195.993850484607 8302254.115385746583) (579196.125050751143 8302254.385188446380)) 0.000000000000)
("1A32C" ((579189.303683741833 8302273.971645710990) (579184.244623046252 8302263.568098068237)) ((579184.644457883551 8302263.704325041734) (579184.513257615385 8302263.434522341937) (579183.975988477119 8302263.701673794538) (579184.107188743656 8302263.971476494335)) 0.000000000000)
("1A32B" ((579270.945980843506 8302246.629808455706) (579241.138104797108 8302214.161523682065)) ((579241.560199964442 8302214.177690160461) (579241.357307257829 8302213.956688900478) (579240.918902336387 8302214.366358463652) (579241.121795041370 8302214.587359723635)) 2442.000000000000)
("1A32A" ((579255.495827040286 8302251.980773199350) (579240.046187901287 8302235.152224849910)) ((579240.468283068622 8302235.168391328305) (579240.265390362008 8302234.947390068322) (579239.826985440566 8302235.357059631497) (579240.029878145549 8302235.578060891479)) 2442.000000000000)
("1A329" ((579190.196870713611 8302274.046179424971) (579186.102732767817 8302284.814854115248)) ((579185.927990571246 8302284.430288321339) (579185.821374640684 8302284.710716654547) (579186.384090894950 8302284.918991575949) (579186.490706826909 8302284.638563242741)) 0.000000000000)
("1A328" ((579205.768231886555 8302275.345561766997) (579194.629019442946 8302304.309240089729)) ((579194.455755728530 8302303.924005913548) (579194.348063403973 8302304.204022645019) (579194.909975481918 8302304.414457534440) (579195.017667807639 8302304.134440802969)) 0.000000000000)
("1A327" ((579221.339593059849 8302276.644944110885) (579211.169378301362 8302303.089078310877)) ((579210.996114586946 8302302.703844134696) (579210.888422262389 8302302.983860866167) (579211.450334340334 8302303.194295755588) (579211.558026666055 8302302.914279024117)) 0.000000000000)
("1A326" ((579236.910954232560 8302277.944326454774) (579227.709737160010 8302301.868916529231)) ((579227.536473445594 8302301.483682353050) (579227.428781121038 8302301.763699084520) (579227.990693198983 8302301.974133973941) (579228.098385524703 8302301.694117242470)) 0.000000000000)
("1A325" ((579260.926225914853 8302250.088624323718) (579255.695334234857 8302263.689753194340)) ((579255.522070520441 8302263.304519018158) (579255.414378195885 8302263.584535749629) (579255.976290273829 8302263.794970639050) (579256.083982599550 8302263.514953907579)) 2442.000000000000)
("1A31E" ((579276.283363381517 8302246.909169465303) (579322.172448789701 8302253.037722016685)) ((579321.837988329353 8302253.295717919245) (579322.135359772597 8302253.335432296619) (579322.209537806804 8302252.740011736751) (579321.912166364607 8302252.700297356583)) 0.000000000000)
("1A31D" ((579283.542758638621 8302273.228853936307) (579322.741518768598 8302278.463904042728)) ((579322.407058308250 8302278.721899945289) (579322.704429751495 8302278.761614322662) (579322.778607785702 8302278.166193762794) (579322.481236343505 8302278.126479382627)) 0.000000000000)
("1A31C" ((579280.616970360046 8302262.621107478626) (579326.494808542193 8302268.748157951050)) ((579326.160348081845 8302269.006153853610) (579326.457719525089 8302269.045868230984) (579326.531897559296 8302268.450447671115) (579326.234526117099 8302268.410733290948)) 0.000000000000)
("1A31B" ((579192.221682640025 8302388.248884638771) (579222.499023626558 8302419.050283784047)) ((579192.644083617255 8302388.250645256601) (579192.433771238429 8302388.036692666821) (579192.009594041621 8302388.461076610722) (579192.219906418701 8302388.675029199570)) -106.315282261078)
("1A31A" ((579185.292838232592 8302402.970619679429) (579209.679602992488 8302427.406553372741)) ((579185.715240430785 8302402.969181544147) (579185.503313890425 8302402.756827714853) (579185.082362574758 8302403.184411644004) (579185.294289113488 8302403.396765472367)) 2442.000000000000)
("1A319" ((579170.081380894291 8302431.781230746768) (579182.924545241403 8302444.846692193300)) ((579170.503781871521 8302431.782991364598) (579170.293469492695 8302431.569038774818) (579169.869292295887 8302431.993422718719) (579170.079604672967 8302432.207375307567)) 2442.000000000000)
("1A318" ((579174.279574583052 8302413.722944777459) (579196.302074116655 8302436.126622784883)) ((579174.701975560281 8302413.724705395289) (579174.491663181456 8302413.510752805509) (579174.067485984648 8302413.935136749409) (579174.277798361727 8302414.149089338258)) 2442.000000000000)
("1A317" ((579220.515599114820 8302348.527128199115) (579195.683008804568 8302386.321407707408)) ((579195.595575326821 8302385.908151040785) (579195.430832462152 8302386.158883559518) (579195.935185146984 8302386.483931855299) (579196.099928012351 8302386.233199339360)) 2442.000000000000)
("1A316" ((579203.997829710483 8302346.351709779352) (579181.893020338262 8302380.002786672674)) ((579181.805539636756 8302379.589540000074) (579181.640825425391 8302379.840291342698) (579182.145215251134 8302380.165282002650) (579182.309929463547 8302379.914530661888)) 2442.000000000000)
("1A315" ((579173.793990985258 8302342.373812673613) (579169.232746653957 8302349.317585909739)) ((579169.145265952451 8302348.904339237139) (579168.980551741086 8302349.155090579763) (579169.484941566829 8302349.480081239715) (579169.649655779242 8302349.229329898953)) 0.000000000000)
("1A314" ((579190.311760389595 8302344.549231094308) (579175.928404143662 8302366.445616574958)) ((579175.840923442156 8302366.032369902357) (579175.676209230791 8302366.283121244982) (579176.180599056534 8302366.608111904934) (579176.345313268946 8302366.357360564172)) 0.000000000000)
("1A313" ((579206.507498067338 8302304.294014126062) (579226.920605821186 8302346.818216027692)) ((579206.906637809938 8302304.432264446281) (579206.776805728907 8302304.161800701171) (579206.238190405769 8302304.426227550954) (579206.368022484821 8302304.696691296995)) 0.000000000000)
("1A312" ((579190.707430471666 8302306.041114695370) (579210.466914157849 8302347.203699238598)) ((579191.106570214266 8302306.179365015589) (579190.976738133235 8302305.908901270479) (579190.438122810097 8302306.173328120261) (579190.567954889149 8302306.443791866302)) 0.000000000000)
("1A311" ((579181.508647853858 8302321.539887894876) (579192.705259732436 8302344.864459039643)) ((579181.907787596458 8302321.678138215095) (579181.777955515427 8302321.407674469985) (579181.239340192289 8302321.672101319768) (579181.369172271341 8302321.942565065809)) 0.000000000000)
("1A310" ((579171.188931477256 8302334.521095043980) (579174.943605306558 8302342.525218842551)) ((579171.586820575059 8302334.662904604338) (579171.459409207921 8302334.391292102635) (579170.918453746592 8302334.650897985324) (579171.045865111751 8302334.922510486096)) 0.000000000000)
("1A30F" ((579270.545403351774 8302267.978549784981) (579279.121957797790 8302257.480799850076)) ((579270.501218497870 8302267.558462432586) (579270.311405709013 8302267.790794333443) (579270.779400994536 8302268.166305236518) (579270.969213783857 8302267.933973336592)) 2442.000000000000)
("1A30E" ((579275.586576482048 8302285.516619006172) (579284.068441132433 8302275.134769908153)) ((579275.542391628143 8302285.096531653777) (579275.352578839404 8302285.328863554634) (579275.820574124693 8302285.704374457709) (579276.010386914248 8302285.472042557783)) 2442.000000000000)
("1A30D" ((579279.625382543774 8302297.199324837886) (579287.471324921120 8302281.996214626357)) ((579279.495163298328 8302296.797493239865) (579279.357576479786 8302297.064095704816) (579279.893188607763 8302297.334553970955) (579280.030775427469 8302297.067951506935)) 2442.000000000000)
("1A30C" ((579286.396758596878 8302316.786300120875) (579298.261285076849 8302293.796365319751)) ((579286.266539351433 8302316.384468522854) (579286.128952532890 8302316.651070987806) (579286.664564660867 8302316.921529253945) (579286.802151480573 8302316.654926789925)) 2442.000000000000)
("1A30B" ((579305.522562693222 8302345.141951158643) (579319.841205389705 8302317.396666710265)) ((579305.392343447777 8302344.740119560622) (579305.254756629234 8302345.006722025573) (579305.790368757211 8302345.277180291712) (579305.927955576917 8302345.010577827692)) 2442.000000000000)
("1A30A" ((579293.216210901737 8302336.280117880553) (579309.051245232695 8302305.596516015008)) ((579293.085991656291 8302335.878286282532) (579292.948404837749 8302336.144888747483) (579293.484016965725 8302336.415347013623) (579293.621603785432 8302336.148744549602)) 2442.000000000000)
("1A309" ((579255.024989828002 8302287.531015061773) (579275.663755730377 8302289.365203040652)) ((579275.341001917492 8302289.637701961212) (579275.639835813316 8302289.664259630255) (579275.687675647438 8302289.066146451049) (579275.388841752661 8302289.039588780142)) 0.000000000000)
("1A308" ((579257.866708692163 8302302.842680408619) (579281.236258033430 8302304.919555873610)) ((579280.913504220429 8302305.192054794170) (579281.212338116253 8302305.218612463214) (579281.260177950608 8302304.620499284007) (579280.961344055715 8302304.593941613100)) 0.000000000000)
("1A307" ((579269.233584154048 8302364.089341809042) (579286.011845942936 8302365.543686557561)) ((579285.689685294288 8302365.816886487417) (579285.988576219301 8302365.842794441618) (579286.035115666571 8302365.244578673504) (579285.736224742723 8302365.218670718372)) 0.000000000000)
("1A306" ((579266.391865288955 8302348.777676457539) (579298.142493726336 8302351.599386891350)) ((579297.819739913335 8302351.871885811910) (579298.118573809159 8302351.898443480954) (579298.166413643514 8302351.300330301747) (579297.867579748621 8302351.273772630841)) 0.000000000000)
("1A305" ((579263.550146423746 8302333.466011108831) (579291.978412700235 8302335.992459856905)) ((579291.655658887350 8302336.264958777465) (579291.954492783174 8302336.291516446508) (579292.002332617296 8302335.693403267302) (579291.703498722520 8302335.666845596395)) 0.000000000000)
("1A304" ((579260.708427558420 8302318.154345760122) (579286.607335366425 8302320.456007864326)) ((579286.284581553540 8302320.728506784886) (579286.583415449364 8302320.755064453930) (579286.631255283486 8302320.156951274723) (579286.332421388710 8302320.130393603817)) 0.000000000000)
("1A303" ((579232.811552068219 8302395.526270493865) (579272.748386909836 8302373.295551318675)) ((579272.634475436644 8302373.702306603082) (579272.896611276548 8302373.556389475241) (579272.600162543124 8302373.034713162109) (579272.338026703103 8302373.180630289949)) 0.000000000000)
("1A302" ((579242.356194320018 8302407.380614344031) (579280.283555335132 8302386.123786837794)) ((579280.170826970832 8302386.530871597119) (579280.432537453598 8302386.384192933328) (579280.134573216666 8302385.863380742259) (579279.872862733784 8302386.010059403256)) 0.000000000000)
("1A301" ((579270.953727484564 8302442.963904275559) (579280.037709944649 8302437.860557518899)) ((579279.925394846243 8302438.267756492831) (579280.186956309248 8302438.120812257752) (579279.888463580050 8302437.600302780047) (579279.626902116928 8302437.747247013263)) 0.000000000000)
("1A300" ((579261.421216429910 8302431.102807630785) (579280.189071439905 8302420.683658708818)) ((579280.074697761796 8302421.090284270234) (579280.336999267573 8302420.944665153511) (579280.041143612238 8302420.422652264126) (579279.778842106345 8302420.568271378987)) 0.000000000000)
("1A2FF" ((579251.888705375604 8302419.241710988805) (579280.098803326255 8302403.538644683547)) ((579279.984891853062 8302403.945399967954) (579280.247027692967 8302403.799482840113) (579279.950578959542 8302403.277806526981) (579279.688443119521 8302403.423723654822)) 0.000000000000)
("1A2FE" ((579231.915641760686 8302427.748307732865) (579244.284710577689 8302409.780225273222)) ((579231.837145819096 8302427.333260660060) (579231.667031049379 8302427.580380008556) (579232.164252471994 8302427.916235457174) (579232.334367242409 8302427.669116110541)) 0.000000000000)
("1A2FD" ((579256.963831090368 8302467.924458756112) (579272.673437675345 8302445.103702345863)) ((579256.885335148778 8302467.509411683306) (579256.715220379177 8302467.756531031802) (579257.212441801559 8302468.092386480421) (579257.382556572091 8302467.845267133787)) 2442.000000000000)
("1A2FC" ((579249.648603921407 8302452.097255725414) (579262.864635338890 8302432.898822455667)) ((579249.570107979816 8302451.682208652608) (579249.399993210100 8302451.929328001104) (579249.897214632714 8302452.265183449723) (579250.067329403129 8302452.018064103089)) 2442.000000000000)
("1A2FB" ((579235.459840127151 8302446.254981605336) (579253.055833003251 8302420.693942567334)) ((579235.381344185560 8302445.839934532531) (579235.211229415960 8302446.087053881027) (579235.708450838341 8302446.422909329645) (579235.878565608873 8302446.175789983012)) 2442.000000000000)
("1A2FA" ((579222.705941428198 8302427.854112034664) (579220.120207871776 8302420.600901890546)) ((579222.323507331894 8302427.674752486870) (579222.424249808304 8302427.957343994640) (579222.987633048091 8302427.750880074687) (579222.886890573543 8302427.468288565986)) -106.315282261078)
("1A2F9" ((579215.782415061607 8302455.047862283885) (579206.635753012146 8302429.390670422465)) ((579215.399980965303 8302454.868502736092) (579215.500723441713 8302455.151094243862) (579216.064106681501 8302454.944630323909) (579215.963364206953 8302454.662038815208)) -106.315282261078)
("1A2F8" ((579187.008257905371 8302467.563521442004) (579179.666843294632 8302446.970207482576)) ((579186.625823809183 8302467.384161894210) (579186.726566285477 8302467.666753401980) (579187.289949525264 8302467.460289482027) (579187.189207050833 8302467.177697973326)) -106.315282261078)
("1A2F7" ((579201.653333222726 8302462.029395417310) (579193.151298153447 8302438.180438950658)) ((579201.270899126539 8302461.850035869516) (579201.371641602833 8302462.132627377287) (579201.935024842620 8302461.926163457334) (579201.834282368072 8302461.643571948633)) -106.315282261078)
("1A2F6" ((579226.520425140858 8302452.154471696354) (579195.671838812181 8302465.790900095366)) ((579195.822524498915 8302465.396286982112) (579195.548126443638 8302465.517582960427) (579195.795551180723 8302466.064217230305) (579196.069949235884 8302465.942921253853)) 2442.000000000000)
("1A2F5" ((579232.158625980956 8302482.462482615374) (579214.982047280064 8302490.055283890106)) ((579215.132732967031 8302489.660670775920) (579214.858334911754 8302489.781966754235) (579215.105759648839 8302490.328601024114) (579215.380157703999 8302490.207305047661)) 2442.000000000000)
("1A2F4" ((579229.339525561314 8302467.308477154002) (579202.314884941559 8302479.254553803243)) ((579202.465570628294 8302478.859940689988) (579202.191172573017 8302478.981236668304) (579202.438597310102 8302479.527870938182) (579202.712995365262 8302479.406574961729)) 2442.000000000000)
("1A2F3" ((579224.883850873448 8302443.357106691226) (579248.621450613951 8302452.258426643908)) ((579248.237684286083 8302452.434917693958) (579248.518595063477 8302452.540255922824) (579248.724306164426 8302451.976597364992) (579248.443395388429 8302451.871259136125)) 0.000000000000)
("1A2F2" ((579231.291204284993 8302477.799678473733) (579254.115209563752 8302486.358411281370)) ((579253.731443235767 8302486.534902331419) (579254.012354013277 8302486.640240560286) (579254.218065114226 8302486.076582002454) (579253.937154338346 8302485.971243773587)) 0.000000000000)
("1A2F1" ((579228.087527579512 8302460.578392581083) (579257.578102070838 8302471.637010221370)) ((579257.194335742854 8302471.813501271419) (579257.475246520364 8302471.918839500286) (579257.680957621313 8302471.355180942453) (579257.400046845316 8302471.249842713587)) 0.000000000000)
("1A2EE" ((579249.646039757063 8302276.157818636857) (579235.259618565789 8302301.747023856267)) ((579235.143841685960 8302301.340795596130) (579234.996815870632 8302301.602311210707) (579235.522421260946 8302301.891736501828) (579235.669447077322 8302301.630220889114)) 0.000000000000)))
; Remates para Xref_Tuberias de coleccion_copy.dwg.
; Comando: REMATES300. No guarda el archivo. Incluye comprobacion de duplicados.
(defun rt300-points (data / ps)
  (foreach item data (if (= (car item) 10) (setq ps (cons (cdr item) ps))))
  (reverse ps))
(defun rt300-same (a b / ok)
  (setq ok (= (length a) (length b)))
  (while (and ok a) (setq ok (equal (car a) (car b) 0.000001) a (cdr a) b (cdr b))) ok)
(defun rt300-existing (/ ss i e data found)
  (setq ss (ssget "_X" '((0 . "LWPOLYLINE") (8 . "WWW_Tub. 300 Perf.") (410 . "Model"))) i 0)
  (if ss (repeat (sslength ss)
    (setq e (ssname ss i) i (1+ i) data (entget e))
    (if (= (cdr (assoc 90 data)) 4)
      (setq found (cons (list (rt300-points data) (cdr (assoc 38 data))) found))))) found)
(defun rt300-has (ps z caps / found)
  (foreach cap caps
    (if (and (equal z (cadr cap) 0.000001)
      (or (rt300-same ps (car cap)) (rt300-same ps (reverse (car cap))))) (setq found T))) found)
(defun rt300-entity (template ps z / result)
  (foreach item template
    (cond ((member (car item) '(-1 5 330)) nil)
      ((= (car item) 10) (setq result (cons (cons 10 (car ps)) result) ps (cdr ps)))
      ((= (car item) 38) (setq result (cons (cons 38 z) result)))
      (T (setq result (cons item result)))))
  (if (entmake (reverse result)) (entlast)))
(defun c:REMATES300 (/ *error* template e data valid caps made started item)
  (defun *error* (msg)
    (foreach e made (if (entget e) (entdel e)))
    (if started (command-s "_.UNDO" "_End"))
    (princ (strcat "\nREMATES300 cancelado: " msg)) (princ))
  (setq rt300-created 0 rt300-skipped 0 valid T)
  (if (and (setq e (handent "1A491"))
           (= (cdr (assoc 8 (entget e))) "WWW_Tub. 300 Perf.")
           (= (cdr (assoc 90 (entget e))) 4))
    (setq template (entget e)) (setq valid nil))
  (foreach spec rt300-specs
    (if (not (and (setq e (handent (car spec)))
      (= (cdr (assoc 8 (setq data (entget e)))) "WWW_Tub. 300 Perf.")
      (= (cdr (assoc 90 data)) 2)
      (rt300-same (rt300-points data) (cadr spec))
      (equal (cdr (assoc 38 data)) (cadddr spec) 0.000001))) (setq valid nil)))
  (if (not valid)
    (princ "\nREMATES300: el dibujo no coincide con la copia revisada. No se hizo ningun cambio.")
    (progn
      (setq caps (rt300-existing))
      (command-s "_.UNDO" "_Begin") (setq started T)
      (foreach spec rt300-specs
        (if (rt300-has (caddr spec) (cadddr spec) caps)
          (setq rt300-skipped (1+ rt300-skipped))
          (if (setq e (rt300-entity template (caddr spec) (cadddr spec)))
            (setq made (cons e made) rt300-created (1+ rt300-created)
              caps (cons (list (caddr spec) (cadddr spec)) caps))
            (error "No se pudo crear un remate."))))
      (command-s "_.UNDO" "_End") (setq started nil)
      (princ (strcat "\nREMATES300_OK: creados=" (itoa rt300-created) "; existentes=" (itoa rt300-skipped)))))
  (princ))

(princ "\nComando disponible: REMATES300")
(princ)
