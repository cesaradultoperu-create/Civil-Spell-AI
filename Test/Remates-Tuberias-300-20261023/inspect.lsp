(defun rt-json (v)
  (cond ((null v) "null")
    ((= (type v) 'STR) (vl-prin1-to-string v))
    ((= (type v) 'INT) (itoa v))
    ((= (type v) 'REAL) (rtos v 2 12))
    ((listp v) (strcat "[" (rt-join (mapcar 'rt-json v)) "]"))
    (T "null")))
(defun rt-join (items / s)
  (setq s "")
  (foreach x items (setq s (strcat s (if (= s "") "" ",") x))) s)
(defun rt-dump (/ f ss i e data row)
  (setq f (open (if rt-output rt-output "C:/Users/Cesar Ugaz/civil3D traductor/repos/CivilSpellAI/Test/Remates-Tuberias-300-20261023/entities.jsonl") "w"))
  (setq ss (ssget "_X" '((410 . "Model"))) i 0)
  (if ss (repeat (sslength ss)
    (setq e (ssname ss i) i (1+ i) data nil)
    (foreach row (entget e)
      (if (member (car row) '(0 5 6 8 10 11 38 39 40 41 42 43 48 62 67 70 90 100 210 410))
        (setq data (cons (if (listp (cdr row)) row (list (car row) (cdr row))) data))))
    (write-line (rt-json (reverse data)) f)))
  (close f) (princ "\nREMATES_INSPECT_OK\n"))
(rt-dump)
(princ)
