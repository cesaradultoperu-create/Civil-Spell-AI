(defun c:TUBERIAVISTALIMPIA (/ lay refs model h e d wasEcho)
  (vl-load-com)
  (setq wasEcho (getvar "CMDECHO"))
  (setvar "CMDECHO" 0)
  (setq lay "REFERENCIAS_TOP_FRONT_2D" refs (ssadd))
  (if (not (tblsearch "LAYER" lay))
    (entmake (list '(0 . "LAYER") '(100 . "AcDbSymbolTableRecord") '(100 . "AcDbLayerTableRecord")
                   (cons 2 lay) '(70 . 0) '(62 . 5) '(6 . "Continuous"))))
  (foreach h '("7092" "7093" "7094" "7095" "7351" "7352")
    (if (setq e (handent h))
      (progn (setq d (entget e)) (entmod (subst (cons 8 lay) (assoc 8 d) d)) (entupd e) (ssadd e refs))))
  (setq model (ssget "_X" '((0 . "INSERT") (2 . "CIVILSPELLAI_REFERENCIAS_3D_*"))))
  (if (and (= (sslength refs) 6) model)
    (progn
      (command "_.-LAYER" "_Thaw" lay "_ON" lay "")
      (command "_.VSCURRENT" "_2dwireframe")
      (command "_.VPOINT" '(0 0 1))
      (command "_.ZOOM" "_Object" refs "")
      (command "_.ZOOM" "0.85x")
      (command "_.-VIEW" "_Save" "REFERENCIAS_TOP_FRONT")
      (command "_.-LAYER" "_Freeze" lay "")
      (command "_.VPOINT" '(1 -1 1))
      (command "_.VSCURRENT" "_Shaded")
      (command "_.ZOOM" "_Object" model "")
      (command "_.ZOOM" "0.85x")
      (command "_.-VIEW" "_Save" "MODELO_TUBERIA_3D")
      (command "_.REGENALL")
      (princ "\nPIPE_CLEAN_VIEW_PASS: seis referencias 2D conservadas en capa separada; modelo 3D sombreado y encuadrado."))
    (princ "\nPIPE_CLEAN_VIEW_FAIL: no se encuentra la pareja de referencias y su modelo."))
  (setvar "CMDECHO" wasEcho)
  (princ))
(c:TUBERIAVISTALIMPIA)
