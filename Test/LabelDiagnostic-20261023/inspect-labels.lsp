(vl-load-com)
(defun csdiag-get (obj prop / result)
  (setq result (vl-catch-all-apply 'vlax-get-property (list obj prop)))
  (if (vl-catch-all-error-p result) nil result))
(defun csdiag-out (value)
  (prin1 value csdiag-file) (write-line "" csdiag-file))
(defun csdiag-prop (obj prop / val)
  (setq val (csdiag-get obj prop))
  (list prop (if (= (type val) 'VLA-OBJECT) (csdiag-get val 'Value) val)))
(defun csdiag-run (/ app doc civil cdoc styles style components obj h e pt hit original-tab)
  (setq csdiag-file (open "C:/Users/Cesar Ugaz/civil3D traductor/repos/CivilSpellAI/Test/LabelDiagnostic-20261023/live-report.txt" "w"))
  (setq app (vlax-get-acad-object) doc (vla-get-ActiveDocument app))
  (csdiag-out (list 'document (vla-get-FullName doc)))
  (setq original-tab (getvar "CTAB"))
  (csdiag-out (list 'original-layout original-tab))
  (if (/= original-tab "Model") (setvar "CTAB" "Model"))
  (foreach key '("CTAB" "CMDNAMES" "OSMODE" "OSNAPZ" "PICKFIRST" "PICKBOX" "INSUNITS" "UCSORG" "UCSXDIR" "UCSYDIR" "VIEWTWIST" "VIEWDIR")
    (csdiag-out (list key (getvar key))))
  (setq civil (vla-GetInterfaceObject app "AeccXUiLand.AeccApplication.13.6") cdoc (csdiag-get civil 'ActiveDocument))
  (setq styles (csdiag-get cdoc 'GeneralLineLabelStyles))
  (csdiag-out (list 'civil-document (csdiag-get cdoc 'Name) 'styles-count (csdiag-get styles 'Count)))
  (foreach name '("Este" "Norte" "Standard")
    (setq style (vl-catch-all-apply 'vlax-get-property (list styles 'Item name)))
    (if (not (vl-catch-all-error-p style))
      (progn
        (csdiag-out (list 'style name))
        (setq obj (csdiag-get style 'LabelProperties))
        (foreach key '(Visibility TagDisplayMode Layer TextStyle) (csdiag-out (csdiag-prop obj key)))
        (setq components (csdiag-get style 'TextComponents))
        (if components (vlax-for obj components
          (csdiag-out (list 'component (csdiag-get obj 'Name)))
          (foreach key '(Visibility Contents Height Mode Color) (csdiag-out (csdiag-prop obj key))))))))
  (foreach h '("22C61" "22C60" "22C5F" "24726" "2472F" "24732")
    (if (setq e (handent h))
      (progn
        (csdiag-out (list 'entity h (entget e)))
        (if (= (cdr (assoc 0 (entget e))) "LWPOLYLINE")
          (progn
            (setq pt (vlax-curve-getPointAtParam e 0.5))
            (setq hit (nentselp (trans pt 0 1)))
            (csdiag-out (list 'pick-test h pt (if hit (entget (car hit)) nil))))))))
  (close csdiag-file) (setq csdiag-file nil)
  (if (/= original-tab "Model") (setvar "CTAB" original-tab))
  (princ "\nCS_LABEL_READ_ONLY_REPORT_DONE\n") (princ))
(csdiag-run)
