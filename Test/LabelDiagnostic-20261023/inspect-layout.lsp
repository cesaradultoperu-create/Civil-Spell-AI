(vl-load-com)
(defun cs-layout-report (/ f ss i e obj doc lo hi value)
  (setq f (open "C:/Users/Cesar Ugaz/civil3D traductor/repos/CivilSpellAI/Test/LabelDiagnostic-20261023/layout-report.txt" "w"))
  (foreach key '("DWGNAME" "CTAB" "CVPORT" "TILEMODE" "VIEWTWIST" "VIEWDIR" "VIEWCTR" "VIEWSIZE" "UCSORG" "UCSXDIR" "UCSYDIR" "SELECTIONCYCLING" "AECCVIEWPORTOPT" "AECCLABELOPTFLAGS" "QTEXTMODE")
    (prin1 (list key (getvar key)) f) (write-line "" f))
  (setq ss (ssget "_X" '((0 . "VIEWPORT") (410 . "Layout1"))))
  (if ss (progn (setq i 0) (repeat (sslength ss)
    (setq e (ssname ss i) i (1+ i))
    (prin1 (list 'viewport (entget e)) f) (write-line "" f))))
  (setq doc (vla-get-ActiveDocument (vlax-get-acad-object)))
  (vlax-for obj (vla-get-ModelSpace doc)
    (if (= (vla-get-ObjectName obj) "AeccDbSurfaceTin")
      (progn (prin1 (list 'surface (vla-get-Handle obj) (vla-get-Visible obj)) f) (write-line "" f))))
  (foreach h '("24C8B" "24C8C")
    (if (setq e (handent h))
      (progn
        (setq obj (vlax-ename->vla-object e))
        (prin1 (list 'label h (vla-get-Visible obj) (vla-get-Layer obj)) f) (write-line "" f)
        (setq value (vl-catch-all-apply 'vla-GetBoundingBox (list obj 'lo 'hi)))
        (if (not (vl-catch-all-error-p value))
          (progn (prin1 (list 'bounds (vlax-safearray->list lo) (vlax-safearray->list hi)) f) (write-line "" f))))))
  (close f) (princ "\nCS_LAYOUT_READ_ONLY_DONE\n") (princ))
(cs-layout-report)
