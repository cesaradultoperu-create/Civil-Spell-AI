(vl-load-com)
(defun c:CSGRILLAPRUEBA (/ *error* csgrestore doc states obj before after ss file)
  (defun csgrestore ()
    (foreach entry states
      (vl-catch-all-apply 'vla-put-Visible (list (car entry) (cadr entry))))
    (setq states nil)
    (vl-catch-all-apply 'vla-Regen (list doc 0)))
  (defun *error* (msg)
    (csgrestore)
    (if file (progn (write-line (strcat "END " msg) file) (close file) (setq file nil)))
    (princ "\nSuperficies restauradas.\n") (princ))
  (setq doc (vla-get-ActiveDocument (vlax-get-acad-object)))
  (setq file (open "C:/Users/Cesar Ugaz/civil3D traductor/repos/CivilSpellAI/Test/LabelDiagnostic-20261023/grid-only-trial.txt" "w"))
  (write-line (strcat "DRAWING " (vla-get-FullName doc)) file)
  (setq ss (ssget "_X" '((0 . "AECC_GENERAL_SEGMENT_LABEL"))))
  (setq before (if ss (sslength ss) 0))
  (write-line (strcat "LABELS_BEFORE " (itoa before)) file)
  (vlax-for obj (vla-get-ModelSpace doc)
    (if (= (vla-get-ObjectName obj) "AeccDbSurfaceTin")
      (progn
        (setq states (cons (list obj (vla-get-Visible obj)) states))
        (vla-put-Visible obj :vlax-false))))
  (write-line (strcat "SURFACES_TEMPORARILY_HIDDEN " (itoa (length states))) file)
  (vla-Regen doc 0)
  (princ "\nPrueba: superficies ocultas temporalmente. Selecciona la polilinea de cuadricula. Enter o Esc restaura las superficies.\n")
  (command "_ADDSEGMENTLABEL")
  (while (> (logand (getvar "CMDACTIVE") 1) 0) (command pause))
  (setq ss (ssget "_X" '((0 . "AECC_GENERAL_SEGMENT_LABEL"))))
  (setq after (if ss (sslength ss) 0))
  (write-line (strcat "LABELS_AFTER " (itoa after)) file)
  (csgrestore)
  (write-line "SURFACES_RESTORED" file)
  (close file) (setq file nil)
  (princ "\nSuperficies restauradas.\n") (princ))
(princ)
