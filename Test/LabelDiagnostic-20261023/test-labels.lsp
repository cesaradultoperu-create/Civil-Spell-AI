(vl-load-com)
(defun cslabel-count (/ ss)
  (if (setq ss (ssget "_X" '((0 . "AECC_GENERAL_SEGMENT_LABEL")))) (sslength ss) 0))
(defun cslabel-test (/ doc file ent pt before after previous-error)
  (setq doc (vla-get-ActiveDocument (vlax-get-acad-object)))
  (if (= (strcase (vla-get-Name doc)) "DIAGNOSTICO-LABELS.DWG")
    (progn
      (setq file (open "C:/Users/Cesar Ugaz/civil3D traductor/repos/CivilSpellAI/Test/LabelDiagnostic-20261023/native-test.txt" "w"))
      (write-line (strcat "DRAWING " (vla-get-FullName doc)) file)
      (setvar "CTAB" "Model")
      (setq ent (handent "22C61") pt (vlax-curve-getPointAtParam ent 0.5))
      (command "_.ZOOM" "_C" (trans pt 0 1) 100.0)
      (write-line (strcat "OSMODE " (itoa (getvar "OSMODE"))) file)
      (setq before (cslabel-count))
      (command "_AddSegmentLabel" (trans pt 0 1) "")
      (setq after (cslabel-count))
      (write-line (strcat "SINGLE_POINT created=" (itoa (- after before))) file)
      (setq before after)
      (command "_AddSegmentLabel" "_non" (trans pt 0 1) "")
      (setq after (cslabel-count))
      (write-line (strcat "SINGLE_NO_OSNAP created=" (itoa (- after before))) file)
      (setq before after)
      (command "_AddSegmentLabels" ent "")
      (setq after (cslabel-count))
      (write-line (strcat "MULTIPLE_ENTITY created=" (itoa (- after before))) file)
      (close file)
      (princ "\nCS_NATIVE_LABEL_TEST_DONE\n")))
  (princ))
(cslabel-test)
