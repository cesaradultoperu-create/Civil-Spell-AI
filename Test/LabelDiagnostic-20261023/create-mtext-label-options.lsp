;;; One-shot style creation. No timers, hooks, startup changes or scale changes.
;;; Configure csml-config only after reading the actual reference MText.
(vl-load-com)

(defun csml-fail (message)
  (setq csml-failure message)
  (exit))

(defun csml-value (object property)
  (vlax-get-property (vlax-get-property object property) 'Value))

(defun csml-set (object property value)
  (vlax-put-property (vlax-get-property object property) 'Value value))

(defun csml-copy-values (source destination properties)
  (foreach property properties
    (csml-set destination property (csml-value source property))))

(defun csml-write (value)
  (if csml-report (progn (prin1 value csml-report) (write-line "" csml-report))))

(defun csml-style (collection base-name new-name height text-style-name / source target old c tcomp sprops tprops border tborder contents)
  (setq old (vl-catch-all-apply 'vlax-get-property (list collection 'Item new-name)))
  (if (not (vl-catch-all-error-p old))
    (csml-fail (strcat "Destination style already exists: " new-name)))
  (setq source (vlax-get-property collection 'Item base-name))
  (foreach property '(LineComponents TickComponents BlockComponents DirectionArrowComponents)
    (if (> (vlax-get-property (vlax-get-property source property) 'Count) 0)
      (csml-fail "Source contains non-text components; clone requires additional handling.")))
  (setq target (vlax-invoke-method collection 'Add new-name))
  (setq csml-created (cons new-name csml-created))
  (vlax-put-property target 'Description
    (strcat "Dynamic " base-name " coordinates; matches reference MText at current model scale. Reference handle: " (cdr (assoc 'reference-handle csml-config))))
  (setq sprops (vlax-get-property source 'LabelProperties)
        tprops (vlax-get-property target 'LabelProperties))
  (csml-copy-values sprops tprops
    '(TextStyle Visibility ForceInsideCurve ForcedInsertion OrientationReference PlanReadable TagDisplayMode Layer PlanReadableBias PlanReadableFlipAnchors))
  (csml-set tprops 'TextStyle text-style-name)
  (csml-set tprops 'Visibility :vlax-true)
  (csml-set tprops 'TagDisplayMode :vlax-false)
  (csml-set tprops 'Layer (cdr (assoc 'reference-layer csml-config)))
  ;; Add() may include inherited default components; remove only those in this new style.
  (setq old (vlax-get-property target 'TextComponents))
  (while (> (vlax-get-property old 'Count) 0)
    (vlax-invoke-method old 'Remove 0))
  (vlax-for c (vlax-get-property source 'TextComponents)
    (setq tcomp (vlax-invoke-method old 'Add (vlax-get-property c 'Name)))
    (csml-copy-values c tcomp
      '(Mode Color Visibility AnchorComponent AnchorPoint AllowToCurve Attachment Contents Lineweight Angle Height XOffset YOffset Justification SpanOutsideSegments))
    (setq contents (csml-value c 'Contents))
    ;; Coordinate contents are provided explicitly after inspection of drawing units.
    (cond
      ((vl-string-search "General Segment Start Y" contents) (setq contents (cdr (assoc 'north-start csml-config))))
      ((vl-string-search "General Segment End Y" contents) (setq contents (cdr (assoc 'north-end csml-config))))
      ((vl-string-search "General Segment Start X" contents) (setq contents (cdr (assoc 'east-start csml-config))))
      ((vl-string-search "General Segment End X" contents) (setq contents (cdr (assoc 'east-end csml-config)))))
    (csml-set tcomp 'Contents contents)
    (csml-set tcomp 'Height height)
    (csml-set tcomp 'Color (cdr (assoc 'reference-color csml-config)))
    (setq border (vlax-get-property c 'BorderStyle)
          tborder (vlax-get-property tcomp 'BorderStyle))
    (csml-copy-values border tborder '(Visibility Color Gap Linetype Lineweight Type))
    (vlax-put-property tborder 'BackgroundMask :vlax-true)
    (csml-set tborder 'Visibility :vlax-false)
    (csml-set tborder 'Gap (cdr (assoc 'mask-gap csml-config)))
    (if (not (equal height (csml-value tcomp 'Height) 1e-10))
      (csml-fail "Component text height verification failed."))
    (if (/= contents (csml-value tcomp 'Contents))
      (csml-fail "Component dynamic text verification failed."))
    (csml-write (list 'component new-name (vlax-get-property tcomp 'Name)
      'height (csml-value tcomp 'Height) 'contents (csml-value tcomp 'Contents))))
  (setq sprops (vlax-get-property source 'DraggedComponentStyle)
        tprops (vlax-get-property target 'DraggedComponentStyle))
  (csml-copy-values sprops tprops
    '(DisplayBorder Color Gap Linetype Lineweight StackText TextHeight LeaderJustification LeaderAttachment BorderType))
  (csml-set tprops 'TextHeight height)
  (setq sprops (vlax-get-property source 'DraggedLeaderStyle)
        tprops (vlax-get-property target 'DraggedLeaderStyle))
  (csml-copy-values sprops tprops
    '(ArrowheadSize ArrowheadStyle Color Linetype Lineweight Spline Visibility))
  (csml-write (list 'created new-name 'handle (vlax-get-property target 'Handle)))
  target)

(defun c:CSCREAROPCIONESMTEXT (/ *error* app doc civil cdoc collection ref height scale saved-scale saved-tab)
  (defun *error* (message)
    (if csml-failure (setq message csml-failure))
    (if collection
      (foreach name csml-created
        (vl-catch-all-apply 'vlax-invoke-method (list collection 'Remove name))))
    (if doc (vl-catch-all-apply 'vla-EndUndoMark (list doc)))
    (csml-write (list 'error message 'created-styles-removed csml-created))
    (if csml-report (progn (close csml-report) (setq csml-report nil)))
    (setq csml-created nil csml-failure nil)
    (princ (strcat "\nStyle creation stopped: " message)) (princ))
  (if (not (and (boundp 'csml-config) csml-config))
    (csml-fail "Reference configuration has not been supplied."))
  (setq app (vlax-get-acad-object) doc (vla-get-ActiveDocument app))
  (if (/= (strcase (vla-get-FullName doc)) (strcase (cdr (assoc 'drawing csml-config))))
    (csml-fail "The active drawing is not the authorized target drawing."))
  (setq saved-scale (getvar "CANNOSCALE") saved-tab (getvar "CTAB"))
  (if (/= saved-scale (cdr (assoc 'annotation-scale csml-config)))
    (csml-fail "Annotation scale differs from the inspected reference."))
  (setq ref (handent (cdr (assoc 'reference-handle csml-config))))
  (if (or (not ref) (/= "MTEXT" (cdr (assoc 0 (entget ref)))))
    (csml-fail "Reference MText is missing."))
  (if (not (equal (cdr (assoc 40 (entget ref))) (cdr (assoc 'reference-height csml-config)) 1e-10))
    (csml-fail "Reference MText height has changed."))
  (setq height (cdr (assoc 'api-height csml-config)))
  (if (or (not (numberp height)) (< height 0.00001) (> height 10.0))
    (csml-fail "Computed paper height is outside supported API limits."))
  (setq civil (vla-GetInterfaceObject app "AeccXUiLand.AeccApplication.13.6")
        cdoc (vlax-get-property civil 'ActiveDocument)
        collection (vlax-get-property cdoc 'GeneralLineLabelStyles))
  (if (/= (strcase (vlax-get-property cdoc 'Name)) (strcase (vla-get-Name doc)))
    (csml-fail "Civil and AutoCAD active documents differ."))
  (setq csml-report (open (cdr (assoc 'report csml-config)) "w") csml-created nil)
  (csml-write (list 'target (vla-get-FullName doc) 'reference (cdr (assoc 'reference-handle csml-config))
    'reference-height (cdr (assoc 'reference-height csml-config)) 'paper-height-api height))
  (vla-StartUndoMark doc)
  (csml-style collection "Norte" (cdr (assoc 'north-name csml-config)) height (cdr (assoc 'text-style csml-config)))
  (csml-style collection "Este" (cdr (assoc 'east-name csml-config)) height (cdr (assoc 'text-style csml-config)))
  (if (or (/= saved-scale (getvar "CANNOSCALE")) (/= saved-tab (getvar "CTAB")))
    (csml-fail "Unexpected change to annotation scale or active tab."))
  (csml-write (list 'verified 'annotation-scale saved-scale 'tab saved-tab 'styles (reverse csml-created)))
  (vla-EndUndoMark doc)
  (close csml-report) (setq csml-report nil csml-created nil)
  (princ "\nMTEXT_MATCHING_LABEL_OPTIONS_CREATED\n") (princ))

(princ)
