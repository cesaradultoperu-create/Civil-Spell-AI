(vl-load-com)
(defun csclick-inspect (/ file pt hit ss i ent closept dist rows)
  (setq file (open "C:/Users/Cesar Ugaz/civil3D traductor/repos/CivilSpellAI/Test/LabelDiagnostic-20261023/click-hit.txt" "w"))
  (setq pt '(579131.588387207 8302352.14478791 0.0))
  (foreach key '("DWGNAME" "CTAB" "CVPORT" "VIEWCTR" "VIEWSIZE" "SCREENSIZE" "VIEWTWIST" "VIEWDIR" "APERTURE" "PICKBOX" "PICKAUTO" "PICKSTYLE" "SELECTIONCYCLING" "OSNAPCOORD" "DYNMODE")
    (prin1 (list key (getvar key)) file) (write-line "" file))
  (setq hit (nentselp (trans pt 0 1)))
  (prin1 (list 'click pt 'hit (if hit (entget (car hit)) nil)) file) (write-line "" file)
  (setq ss (ssget "_X" '((0 . "LWPOLYLINE,LINE,POLYLINE") (410 . "Model"))) i 0 rows nil)
  (if ss (repeat (sslength ss)
    (setq ent (ssname ss i) i (1+ i) closept (vl-catch-all-apply 'vlax-curve-getClosestPointTo (list ent pt)))
    (if (not (vl-catch-all-error-p closept))
      (setq rows (cons (list (distance pt closept) (cdr (assoc 5 (entget ent))) (cdr (assoc 0 (entget ent))) (cdr (assoc 8 (entget ent))) closept) rows)))))
  (setq rows (vl-sort rows '(lambda (a b) (< (car a) (car b)))))
  (setq i 0)
  (foreach row rows (if (< i 8) (progn (prin1 row file) (write-line "" file))) (setq i (1+ i)))
  (close file)
  (princ "\nCS_CLICK_HIT_DONE\n") (princ))
(csclick-inspect)
