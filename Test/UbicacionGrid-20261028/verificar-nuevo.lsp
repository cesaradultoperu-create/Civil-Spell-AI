(vl-load-com)
(setq un-doc (vla-get-ActiveDocument (vlax-get-acad-object)))
(if (= (vla-get-Name un-doc) "Ubicacion_Hidraulica_100x100_1-5000.dwg")
 (progn
  (setq un-f (open "C:/Users/Cesar Ugaz/civil3D traductor/repos/CivilSpellAI/Test/UbicacionGrid-20261028/nuevo-verificado.txt" "w"))
  (write-line (strcat "Archivo=" (vla-get-FullName un-doc)) un-f)
  (write-line (strcat "Layout=" (getvar "CTAB")) un-f)
  (setq un-count 0)
  (vlax-for un-e (vla-get-ModelSpace un-doc)
   (setq un-count (1+ un-count))
   (if (= (vla-get-ObjectName un-e) "AcDbBlockReference")
    (progn
     (write-line (strcat "Referencia=" (vla-get-Name un-e)) un-f)
     (write-line (strcat "Ruta=" (vla-get-Path (vla-Item (vla-get-Blocks un-doc) (vla-get-Name un-e)))) un-f)
     (write-line (strcat "Insercion=" (vl-princ-to-string (vlax-safearray->list (vlax-variant-value (vla-get-InsertionPoint un-e))))) un-f))))
  (write-line (strcat "EntidadesModel=" (itoa un-count)) un-f)
  (vlax-for un-e (vla-get-PaperSpace un-doc)
   (if (= (vla-get-ObjectName un-e) "AcDbViewport")
    (if (> (cdr (assoc 69 (entget (vlax-vla-object->ename un-e)))) 1)
     (progn
      (write-line (strcat "Viewport=" (rtos (vla-get-Width un-e) 2 6) " x " (rtos (vla-get-Height un-e) 2 6) " mm") un-f)
      (write-line (strcat "CentroPapel=" (vl-princ-to-string (vlax-safearray->list (vlax-variant-value (vla-get-Center un-e))))) un-f)
      (write-line (strcat "Escala=" (rtos (vla-get-CustomScale un-e) 2 9) "; modelo metros / papel mm = 1:5000") un-f)
      (write-line (strcat "Bloqueado=" (vl-princ-to-string (vla-get-DisplayLocked un-e))) un-f)))))
  (write-line (strcat "SegmentosCuadricula=" (itoa (sslength (ssget "_X" '((8 . "CUADRICULA_100m") (410 . "UBICACION")))))) un-f)
  (write-line "Paso cuadricula = 100 metros = 20 mm de papel" un-f)
  (vla-Save un-doc)
  (write-line (strcat "DBMOD=" (itoa (getvar "DBMOD"))) un-f)
  (close un-f)
  (princ "\nDIBUJO_NUEVO_VERIFICADO_Y_GUARDADO"))
 (princ "\nERROR: Dibujo activo incorrecto"))
(princ)
