(vl-load-com)
(setq ug-doc (vla-get-ActiveDocument (vlax-get-acad-object)))
(setq ug-vp (vlax-ename->vla-object (handent "14605")))
(vla-put-DisplayLocked ug-vp :vlax-false)
(vla-put-MSpace ug-doc :vlax-true)
(vla-put-ActivePViewport ug-doc ug-vp)
(command "_.ZOOM" "_C" "_non" (trans '(579257.262041458 8302264.916087537 0.0) 0 1) 500.0)
(vla-put-MSpace ug-doc :vlax-false)
(vla-put-DisplayLocked ug-vp :vlax-true)
(vla-Update ug-vp)
(vla-Regen ug-doc 1)
(vla-Save ug-doc)
(setq ug-f (open "C:/Users/Cesar Ugaz/civil3D traductor/repos/CivilSpellAI/Test/UbicacionGrid-20261028/guardado.txt" "w"))
(setq ug-vd (entget (handent "14605")))
(write-line (strcat "Dibujo guardado: " (vla-get-FullName ug-doc)) ug-f)
(write-line (strcat "DBMOD=" (itoa (getvar "DBMOD"))) ug-f)
(write-line (strcat "Papel=" (rtos (cdr (assoc 40 ug-vd)) 2 6) " x " (rtos (cdr (assoc 41 ug-vd)) 2 6)) ug-f)
(write-line (strcat "Modelo altura=" (rtos (cdr (assoc 45 ug-vd)) 2 6)) ug-f)
(write-line (strcat "Centro modelo=" (rtos (car (cdr (assoc 12 ug-vd))) 2 9) "," (rtos (cadr (cdr (assoc 12 ug-vd))) 2 9)) ug-f)
(write-line (strcat "Escala=" (rtos (vla-get-CustomScale ug-vp) 2 9) "; Bloqueado=" (vl-princ-to-string (vla-get-DisplayLocked ug-vp))) ug-f)
(close ug-f)
(princ "\nUG_GUARDADO_VERIFICADO")
(princ)
