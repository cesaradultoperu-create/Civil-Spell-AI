(vl-load-com)
(defun ug-inbox (p b) (and (> (car p) (nth 0 b)) (< (car p) (nth 2 b)) (> (cadr p) (nth 1 b)) (< (cadr p) (nth 3 b))))
(defun ug-hidden (p / r) (setq r nil) (foreach b ug-boxes (if (ug-inbox p b) (setq r T))) r)
(defun ug-segment (p q) (entmakex (list '(0 . "LINE") '(100 . "AcDbEntity") '(67 . 1) '(410 . "A") '(8 . "UBI_CUADRICULA_100m") '(62 . 8) '(420 . 9539985) '(370 . 9) '(100 . "AcDbLine") (cons 10 p) (cons 11 q))))
(defun ug-dashed (p q / d ux uy s t0 p1 p2 mid)
 (setq d (distance p q) ux (/ (- (car q) (car p)) d) uy (/ (- (cadr q) (cadr p)) d) s 0.0)
 (while (< s d)
  (setq t0 (min d (+ s 2.6)) p1 (list (+ (car p) (* s ux)) (+ (cadr p) (* s uy)) 0.0) p2 (list (+ (car p) (* t0 ux)) (+ (cadr p) (* t0 uy)) 0.0) mid (mapcar '(lambda(a b)(/ (+ a b) 2.0)) p1 p2))
  (if (and (not (ug-hidden p1)) (not (ug-hidden p2)) (not (ug-hidden mid))) (ug-segment p1 p2))
  (setq s (+ s 3.6))))
(setq ug-doc (vla-get-ActiveDocument (vlax-get-acad-object)))
(vla-StartUndoMark ug-doc)
(if (not (tblsearch "LAYER" "UBI_CUADRICULA_100m")) (vla-Add (vla-get-Layers ug-doc) "UBI_CUADRICULA_100m"))
(setq ug-cx 579257.262041458 ug-cy 8302264.916087537)
(defun ug-map (x y) (list (+ 775.5 (* 0.2 (- x ug-cx))) (+ 528.5 (* 0.2 (- y ug-cy))) 0.0))
(setq ug-boxes nil)
;; Keep new dashed strokes clear of coordinate labels supplied by the Xref.
(foreach ug-x '(579100.0 579200.0 579300.0 579400.0)
 (setq ug-p1 (ug-map (- ug-x 24.0) 8302390.0) ug-p2 (ug-map (- ug-x 8.0) 8302506.0))
 (setq ug-boxes (cons (list (car ug-p1) (cadr ug-p1) (car ug-p2) (cadr ug-p2)) ug-boxes)))
(foreach ug-y '(8302100.0 8302200.0 8302300.0)
 (setq ug-p1 (ug-map 579382.0 (+ ug-y 11.0)) ug-p2 (ug-map 579496.0 (+ ug-y 27.0)))
 (setq ug-boxes (cons (list (car ug-p1) (cadr ug-p1) (car ug-p2) (cadr ug-p2)) ug-boxes)))
(setq ug-boxes (append '((727.5 547.0 750.0 575.5) (773.5 541.5 781.0 546.7) (740.0 495.0 777.5 503.8)) ug-boxes))
(foreach ug-x '(579100.0 579200.0 579300.0 579400.0 579500.0)
 (setq ug-p1 (ug-map ug-x ug-cy))
 (ug-dashed (list (car ug-p1) 478.5 0.0) (list (car ug-p1) 578.5 0.0)))
(foreach ug-y '(8302100.0 8302200.0 8302300.0 8302400.0 8302500.0)
 (setq ug-p1 (ug-map ug-cx ug-y))
 (ug-dashed (list 725.5 (cadr ug-p1) 0.0) (list 825.5 (cadr ug-p1) 0.0)))
(vla-EndUndoMark ug-doc)
(vla-Regen ug-doc 1)
(setq ug-f (open "C:/Users/Cesar Ugaz/civil3D traductor/repos/CivilSpellAI/Test/UbicacionGrid-20261028/verificacion.txt" "w"))
(setq ug-vd (entget (handent "14605")))
(write-line (strcat "Viewport: " (rtos (cdr (assoc 40 ug-vd)) 2 6) " x " (rtos (cdr (assoc 41 ug-vd)) 2 6) " mm") ug-f)
(write-line (strcat "ViewHeight: " (rtos (cdr (assoc 45 ug-vd)) 2 6) " m") ug-f)
(write-line (strcat "ViewCenter: " (rtos (car (cdr (assoc 12 ug-vd))) 2 9) ", " (rtos (cadr (cdr (assoc 12 ug-vd))) 2 9)) ug-f)
(write-line "Cuadricula: paso 100 m = 20 mm de papel; 5 ejes E + 5 ejes N." ug-f)
(write-line (strcat "Segmentos discontinuos: " (itoa (sslength (ssget "_X" '((8 . "UBI_CUADRICULA_100m") (410 . "A")))))) ug-f)
(setq ug-ref (vlax-ename->vla-object (handent "1CA9D")))
(write-line (strcat "Xref Model insertion: " (vl-princ-to-string (vlax-safearray->list (vlax-variant-value (vla-get-InsertionPoint ug-ref))))) ug-f)
(write-line (strcat "Xref scale: " (rtos (vla-get-XScaleFactor ug-ref) 2 6) ", " (rtos (vla-get-YScaleFactor ug-ref) 2 6) ", " (rtos (vla-get-ZScaleFactor ug-ref) 2 6)) ug-f)
(write-line (strcat "Xref rotation: " (rtos (vla-get-Rotation ug-ref) 2 6)) ug-f)
(write-line (strcat "Xref Path: " (vla-get-Path (vla-Item (vla-get-Blocks ug-doc) (vla-get-Name ug-ref)))) ug-f)
(close ug-f)
(princ "\nUG_GRID_DONE")
(princ)
