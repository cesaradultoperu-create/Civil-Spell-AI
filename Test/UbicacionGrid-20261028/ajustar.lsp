(vl-load-com)
(defun ug-write (s) (write-line s ug-f))
(setq ug-doc (vla-get-ActiveDocument (vlax-get-acad-object)))
(setq ug-f (open "C:/Users/Cesar Ugaz/civil3D traductor/repos/CivilSpellAI/Test/UbicacionGrid-20261028/ajuste.txt" "w"))
(vla-StartUndoMark ug-doc)
(setq ug-vp (vlax-ename->vla-object (handent "14605")))
(setq ug-clip (vlax-ename->vla-object (handent "145FB")))
(setq ug-data (entget (handent "14605")))
(ug-write (strcat "Antes: " (rtos (vla-get-Width ug-vp) 2 6) " x " (rtos (vla-get-Height ug-vp) 2 6)))
(ug-write (strcat "ViewCenter: " (rtos (car (cdr (assoc 12 ug-data))) 2 9) "," (rtos (cadr (cdr (assoc 12 ug-data))) 2 9)))
(vla-put-DisplayLocked ug-vp :vlax-false)
(vla-put-Coordinates ug-clip (vlax-make-variant (vlax-safearray-fill (vlax-make-safearray vlax-vbDouble '(0 . 7)) '(725.5 478.5 825.5 478.5 825.5 578.5 725.5 578.5))))
(vla-put-Width ug-vp 100.0)
(vla-put-Height ug-vp 100.0)
(vla-put-Center ug-vp (vlax-3d-point '(775.5 528.5 0.0)))
(vla-put-CustomScale ug-vp 0.2)
(vla-put-DisplayLocked ug-vp :vlax-true)
(vla-Update ug-vp)
(setq ug-xb (vla-Item (vla-get-Blocks ug-doc) "Xref_Ubicación Hidráulica_ubicacion"))
(ug-write (strcat "Ruta anterior: " (vla-get-Path ug-xb)))
(vla-put-Path ug-xb "Q:\\Proyectos 2026\\1107.001.00.16 - Pad SOTRAMI\\05_Drawing\\Xref\\Xref_Ubicación Hidráulica_ubicacion.dwg")
(setq ug-r (vl-catch-all-apply 'vla-Reload (list ug-xb)))
(ug-write (strcat "Reload: " (vl-princ-to-string ug-r)))
(ug-write (strcat "Ruta final: " (vla-get-Path ug-xb)))
(ug-write (strcat "Dimensiones: " (rtos (vla-get-Width ug-vp) 2 6) " x " (rtos (vla-get-Height ug-vp) 2 6)))
(ug-write (strcat "Escala CAD: " (rtos (vla-get-CustomScale ug-vp) 2 9) "; escala fisica 1:5000 (modelo m / papel mm)"))
(ug-write (strcat "Bloqueado: " (vl-princ-to-string (vla-get-DisplayLocked ug-vp))))
(ug-write (strcat "Recorte: " (vl-princ-to-string (vlax-safearray->list (vlax-variant-value (vla-get-Coordinates ug-clip))))))
(close ug-f)
(vla-EndUndoMark ug-doc)
(vla-Regen ug-doc 1)
(vla-ZoomWindow (vlax-get-acad-object) (vlax-3d-point '(720.0 473.0 0.0)) (vlax-3d-point '(831.0 584.0 0.0)))
(princ "\nUG_AJUSTE_DONE")
(princ)
