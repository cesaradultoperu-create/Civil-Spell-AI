(vl-load-com)
(setq ug-doc (vla-get-ActiveDocument (vlax-get-acad-object)))
(setq ug-out (open "C:/Users/Cesar Ugaz/civil3D traductor/repos/CivilSpellAI/Test/UbicacionGrid-20261028/live.txt" "w"))
(foreach ug-v '("DWGPREFIX" "DWGNAME" "CTAB" "TILEMODE" "CVPORT" "INSUNITS" "CMDNAMES") (write-line (strcat ug-v "=" (vl-princ-to-string (getvar ug-v))) ug-out))
(write-line (strcat "XREF_EXISTS=" (vl-princ-to-string (findfile "Q:/Proyectos 2026/1107.001.00.16 - Pad SOTRAMI/05_Drawing/Xref/Xref_Ubicación Hidráulica_ubicacion.dwg"))) ug-out)
(vlax-for ug-b (vla-get-Blocks ug-doc) (if (= :vlax-true (vla-get-IsXref ug-b)) (write-line (strcat "XREF " (vla-get-Name ug-b) " PATH " (vla-get-Path ug-b)) ug-out)))
(setq ug-ss (ssget "_X" (list (cons 410 (getvar "CTAB")))))
(if ug-ss (progn (setq ug-i 0) (repeat (sslength ug-ss) (setq ug-e (entget (ssname ug-ss ug-i))) (if (or (= "VIEWPORT" (cdr (assoc 0 ug-e))) (and (assoc 10 ug-e) (> (car (cdr (assoc 10 ug-e))) 700.0))) (write-line (vl-princ-to-string ug-e) ug-out)) (setq ug-i (1+ ug-i)))))
(close ug-out)
(princ "\nUG_INSPECT_DONE")
(princ)
